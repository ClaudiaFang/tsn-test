module end-device {
    yang-version 1.1;
    namespace "urn:ietf:params:xml:ns:netconf:1.0:cnc:cnc-model:end-device";
    prefix "edge";

    revision "2018-04-01" { // TODO change revision to date of model creation
        description "Initial revision of peregrine model";
    }

    grouping GroupEndDevice {

        leaf name {
            type string;
        }

        leaf tsn_domain_id {
            type uint16;
        }

        list interface {
            key mac;

            leaf mac {
                type string;
            }

            container switch_port {
                leaf switch_mac {
                    type string;
                }

                leaf port {
                    type string;
                }
            }
        }
    }
}
