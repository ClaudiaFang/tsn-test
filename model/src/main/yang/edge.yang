module edge {
    yang-version 1.1;
    namespace "urn:ietf:params:xml:ns:netconf:1.0:cnc:cnc-model:edge";
    prefix "edge";

    revision "2018-04-01" { // TODO change revision to date of model creation
        description "Initial revision of peregrine model";
    }

    grouping GroupEdge {

        leaf headMAC {
            type string;
        }

        leaf tailMAC {
            type string;
        }

        leaf headPort {
            type string;
        }

        leaf tailPort {
            type string;
        }

        container capacity {

            leaf capacityValue {
                type uint32;
            }

            leaf capacityDesc {
                type string;
            }
        }
    }
}
