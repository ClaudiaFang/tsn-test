module ieee802-dot1q-cc-talker {

    namespace "urn:ieee:std:802.1Q:yang:ieee802-dot1q-cc:talker";
    prefix "dot1q-cc";

    import ietf-inet-types { prefix "inet"; }

    import ieee802-dot1q-cc-base { prefix "base"; }

    organization
        "Institute of Electrical and Electronics Engineers";


    contact
        "WG-URL: http://grouper.ieee.org/groups/802/1/
        WG-EMail: stds-802-1@ieee.org
        Contact: IEEE 802.1 Working Group Chair
        Postal: C/O IEEE 802.1 Working Group
                IEEE Standards Association
                445 Hoes Lane
                P.O. Box 1331
                Piscataway
                NJ 08855-1331
                USA

        E-mail: STDS-802-1-L@LISTSERV.IEEE.ORG";

    description
        "Common typedefs and groupings for TSN user/network configuration
        in IEEE Std 802.1Q.";

    revision 2018-02-15 {
        description
            "Initial revision specified in 46.3 of IEEE Std 802.1Qcc-2018,
            Amendment: Stream Reservation Protocol (SRP) Enhancements
            and Performance Improvements.";
        reference
            "46.3 of IEEE Std 802.1Qcc-2018";
    }

    grouping GroupTalker {
        description
            "This YANG grouping specifies:
            - Talker's behavior for Stream (how/when transmitted)
            - Talker's requirements from the network
            - TSN capabilities of the Talker's interface(s)

            In the fully centralized model of TSN configuration,
            this grouping originates from the CUC, and
            is delivered to the CNC.";
        reference
            "46.2.3 of IEEE Std 802.1Qcc-2018";

        container StreamID {
            description
                "StreamID specifies a unique identifier
                of the stream's configuration, used by protocols in the
                network to associate the user's stream with
                TSN resources.";
            uses base:groupStreamID;
        }

        container StreamRank {
            description
                "Rank of this Stream's configuration relative to other
                Streams in the network. This rank is used to determine
                success/failure of Stream resource configuration,
                and it is unrelated to the Stream's data.";

            reference
                "46.2.3.2 of IEEE Std 802.1Qcc-2018";

            leaf rank {
                type uint8;
                description
                    "The Rank is used by the network to decide which Streams
                    can and cannot exist when TSN resources reach their limit.
                    If a Bridge's Port becomes oversubscribed (e.g. network
                    reconfiguration, IEEE 802.11 bandwidth reduction), the
                    Rank is used to help determine which Streams can be
                    dropped (i.e. removed from Bridge configuration).

                    The only valid values for Rank shall be zero and one.
                    The configuration of a Stream with Rank zero is more
                    important than the configuration of a Stream with
                    Rank one. The Rank value of zero is intended for
                    emergency traffic, and the Rank value of one is
                    intended for non-emergency traffic.

                    NOTE  It is expected that higher layer applications
                    and protocols can use the Rank to indicate the
                    relative importance of Streams based on user
                    preferences. Those user preferences are expressed
                    by means beyond the scope of this standard. When
                    multiple applications exist in a network
                    (e.g. audio/video along with industrial control),
                    it can be challenging for the varied applications
                    and vendors to agree on multiple Rank values.
                    To mitigate such challenges, this Rank uses
                    a simple concept of emergency (zero) and
                    non-emergency (one) that can be applied
                    over all applications. For example, in a network
                    that carries audio Streams for fire safety
                    announcements, all applications are likely to
                    agree that those Streams use Rank of zero.";

                reference
                    "46.2.3.2.1 of IEEE Std 802.1Qcc-2018";
            }
        }

        list EndStationInterfaces {
            key "mac-address interface-name";
            min-elements 1;
            description
                "List of identifiers, one for each physical
                interface (distinct point of attachment) in
                the end station acting as a Talker.

                Although many end stations contain a single interface,
                this list allows for multiple interfaces. Some TSN
                features allow a single Stream to span multiple interfaces
                (e.g. seamless redundancy).

                Each entry of end-station-interfaces is used by the CNC
                to locate the Talker in the topology.

                Since the interface-name leaf is optional, empty string
                can be used for its key value.";

            reference
                "46.2.3.3 of IEEE Std 802.1Qcc-2018";

            uses base:group-interface-id;
        }

        list DataFrameSpecification {
            key "index";
            min-elements 1;
            description
                "data-frame-specification specifies the frame that carries the
                Talker's Stream data. The network uses the specification
                to identify this Stream's frames as TSN, in order to apply
                the required TSN configuration.

                The specification is based on the user's knowledge of the
                frame, without any network specifics. In other words, this
                specifies the frame that the Talker would use in the absence
                of TSN.

                The specification is provided as a list of fields
                that the user knows. The list is ordered
                from start of frame to end of header.
                For example, if the Talker uses a VLAN-tagged
                Ethernet frame (not IP), the list consists of
                ieee802-mac-addresses followed by ieee802-vlan-tag.
                For example, if the Talker uses a UDP/IPv4 packet
                without knowledge of the Ethernet header,
                the list consists of ipv4-tuple.

                This list is optional, and its absence
                indicates that Stream transformation is performed
                in the Talker and Listeners of this Stream
                (46.2.2 of IEEE Sd 802.1Q-2018).";

            reference
                "46.2.3.4 of IEEE Std 802.1Qcc-2018";

            leaf index {
                type uint8;
                description
                    "This index is provided in order to
                    provide a unique key per list entry.
                    The value of index for each entry
                    shall be unique (but not necessarily
                    contiguous).";
            }
            choice field {
                description
                    "One of the following choices is provided
                    for each field that the user knows.
                    Each container name acts as the case name
                    for the choice.";

                container ieee802-mac-addresses {
                    description "IEEE 802 MAC addresses.";
                    uses base:group-ieee802-mac-addresses;
                }
                container ieee802-vlan-tag {
                    description "IEEE 802.1 CTAG";
                    uses base:group-ieee802-vlan-tag;
                }
                container ipv4-tuple {
                    description "IPv4 packet identification";
                    uses base:group-ipv4-tuple;
                }
                container ipv6-tuple {
                    description "IPv6 packet identification";
                    uses base:group-ipv6-tuple;
                }
            }
        }

        container TrafficSpecification {
            description
                "This traffic-specification specifies how the Talker
                transmits frames for the Stream. This is effectively
                the Talker's promise to the network. The network
                uses this traffic spec to allocate resources and
                adjust queue parameters in Bridges.";
            reference
                "46.2.3.5 of IEEE Std 802.1Qcc-2018";
            container interval {
                description
                    "This interval specifies the period of time in
                    which the traffic specification cannot be exceeded.
                    The traffic specification is specified by
                    max-frames-per-interval and max-frame-size.

                    The interval is a rational number of seconds,
                    defined by an integer numerator and an integer
                    denominator.

                    If the time-aware container is not present,
                    the interval specifies a sliding window of time.
                    The Talker's transmission is not synchronized
                    to a time on the network, and therefore
                    the traffic specification cannot be exceeded
                    during any interval in time.

                    If the time-aware container is present,
                    the interval specifies a window of time that is
                    aligned with the time epoch that is synchronized
                    on the network. For example, if IEEE Std
                    802.1AS-2011 is used with the PTP timescale,
                    the first interval begins at 1 January 00:00:00 TAI.
                    If CurrentTime represents the current time, then
                    the start of the next interval (StartOfNextInterval)
                    is:
                    StartOfNextInterval = N * interval
                    where N is the smallest integer for which the relation
                    StartOfNextInterval >= CurrentTime
                    would be TRUE.";

                reference
                    "46.2.3.5.1 of IEEE Std 802.1Qcc-2018";

                leaf numerator {
                    type uint32;
                    description "interval's numerator.";
                }
                leaf denominator {
                    type uint32;
                    description "interval's denominator.";
                }
            }
            leaf max-frames-per-interval {
                type uint16;
                description
                    "max-frames-per-interval specifies the maximum
                    number of frames that the Talker can transmit
                    in one interval.";

                reference
                    "46.2.3.5.2 of IEEE Std 802.1Qcc-2018";
            }
            leaf max-frame-size {
                type uint16;
                description
                    "max-frame-size specifies maximum frame size that
                    the Talker will transmit, excluding any overhead
                    for media-specific framing (e.g., preamble,
                    IEEE 802.3 header, Priority/VID tag, CRC,
                    interframe gap). As the Talker or Bridge determines
                    the amount of bandwidth to reserve on the
                    egress Port (interface), it will calculate the
                    media-specific framing overhead on that Port and
                    add it to the number specified in the max-frame-size
                    leaf.";

                reference
                    "46.2.3.5.3 of IEEE Std 802.1Qcc-2018";
            }
            leaf transmission-selection {
                type uint8;
                description
                    "transmission-selection specifies the algorithm
                    that the Talker uses to transmit this Stream's
                    traffic class. This algorithm is often referred
                    to as the shaper for the traffic class.

                    The value for this leaf uses Table 8-5
                    (Transmission selection algorithm identifiers)
                    of 8.6.8 of IEEE Std 802.1Q-2018.
                    If no algorithm is known, the value
                    zero (strict priority) can be used.

                    The Talker's shaping and scheduling of the
                    Stream is considered to be on the user side
                    of the user/network boundary, and this leaf
                    specifies the Talker's behavior to the network.";

                reference
                    "46.2.3.5.4 of IEEE Std 802.1Qcc-2018";
            }
            container time-aware {
                presence
                    "Specifies that the Talker's traffic is synchronized
                    to a known time on the network
                    (e.g. using IEEE Std 802.1AS)";

                description
                    "The time-aware container provides leafs to specify
                    the Talker's time-aware transmit to the network.

                    The Talker and Listeners of a Stream are assumed to
                    coordinate using user (application) mechanisms, such
                    that each Listener is aware that its Talker transmits
                    in a time-aware manner.

                    If max-frames-per-interval is greater than one,
                    the Talker shall transmit multiple frames as a burst
                    within the interval, with the minimum inter-frame gap
                    allowed by the media.

                    NOTE: Although scheduled traffic (8.6.8.4 of
                    IEEE Std 802.1Q-2018) specifies a valid implementation
                    of a time-aware Talker, the time-aware container
                    is intended to support alternate implementations of
                    scheduling.";

                reference
                    "46.2.3.5 of IEEE Std 802.1Qcc-2018";

                leaf earliest-transmit-offset {
                    type uint32;
                    description
                        "earliest-transmit-offset specifies the
                        earliest offset within the interval at which
                        the Talker is capable of starting
                        transmit of its frames. As part of
                        group-status-talker-listener.interface-configuration,
                        the network will return a specific
                        time-aware-offset to the Talker
                        (within the earliest/latest range),
                        which the Talker uses to schedule its transmit.

                        earliest-transmit-offset is specified
                        as an integer number of nanoseconds.

                        The Talker's transmit offsets
                        include earliest-transmit-offset,
                        latest-transmit-offset, and the
                        time-aware-offset returned to the Talker.
                        Each of the Talker's offsets is specified
                        at the point when the message timestamp point
                        of the first frame of the Stream passes the
                        reference plane marking the boundary between
                        the network media and PHY.
                        The message timestamp point is specified
                        by IEEE Std 802.1AS for various media.";

                    reference
                        "46.2.3.5.5 of IEEE Std 802.1Qcc-2018";
                }
                leaf latest-transmit-offset {
                    type uint32;
                    description
                        "latest-transmit-offset specifies the
                        latest offset within the interval at which
                        the Talker is capable of starting
                        transmit ofits frames. As part of
                        group-status-talker-listener.interface-configuration,
                        the network will return a specific
                        time-aware-offset to the Talker
                        within the earliest/latest range),
                        which the Talker uses to schedule its transmit.

                        latest-transmit-offset is specified
                        as an integer number of nanoseconds.";

                    reference
                        "46.2.3.5.6 of IEEE Std 802.1Qcc-2018";
                }
                leaf jitter {
                    type uint32;
                    description
                        "The jitter leaf specifies the maximum difference
                        in time between the Talker's transmit offsets,
                        and the ideal synchronized network time
                        (e.g. IEEE Std 802.1AS time). Jitter is
                        specified as an unsigned integer number
                        of nanoseconds.

                        The maximum difference means
                        sooner or later than the ideal (e.g. transmit
                        +/- 500 nanoseconds relative to 802.1AS time
                        results in jitter of 500).

                        The ideal synchronized network time refers to
                        time at the source (e.g. 802.1AS grandmaster).
                        The jitter does not include inaccuracies as
                        time is propagated from the time source to the
                        Talker, because those inaccuracies are
                        assumed to be known by the network, and
                        time synchronization is a network technology.
                        The jitter leaf is intended to specify
                        inaccuracies in the Talker's implementation.
                        For example, if the Talker's 802.1AS time is
                        +/- 812 nanoseconds relative to the
                        grandmaster, and the Talker schedules using a
                        100 microsecond timer tick driven by 802.1AS
                        time, Jitter is 50000 (not 50812).

                        The Talker's transmit offsets
                        include earliest-transmit-offset,
                        latest-transmit-offset, and the
                        time-aware-offset returned to the Talker in
                        group-status-talker-listener.interface-configuration.";

                    reference
                        "46.2.3.5.7 of IEEE Std 802.1Qcc-2018";
                }
            }
        }

        container UserToNetworkRequirements {
            description
                "user-to-network-requirements specifies user requirements
                for the Stream, such as latency and redundancy.
                The network (CNC) will merge all
                user-to-network-requirements for a Stream
                to ensure that all requirements are met.";

            reference
                "46.2.3.6 of IEEE Std 802.1Qcc-2018";

            uses base:group-user-to-network-requirements;
        }

        container InterfaceCapabilities {
            description
                "interface-capabilities specifies the network
                capabilities of all interfaces (Ports) contained
                in end-station-interfaces.

                The network may provide configuration
                of these capabilities in
                group-status-talker-listener.interface-configuration.

                NOTE: If an end station contains multiple interfaces
                with different network capabilities, each interface
                should be specified as a distinct Talker or
                Listener (i.e. one entry in end-station-interfaces).
                Use of multiple entries in end-station-interfaces is intended
                for network capabilities that span multiple interfaces
                (e.g. seamless redundancy).";

            reference
                "46.2.3.7 of IEEE Std 802.1Qcc-2018";
    
            uses base:group-interface-capabilities;
        }
    }
}
