module result {
    yang-version 1.1;
    namespace "urn:ietf:params:xml:ns:netconf:1.0:cnc:cnc-model:result";
    prefix "result";

    revision "2018-04-01" { // TODO change revision to date of model creation
        description "Initial revision of peregrine model";
    }

    import ietf-yang-types {
        prefix yang;
    }

    grouping GroupResult{
        leaf result {
            type string;
        }

        leaf message {
            type string;
        }

        leaf timestamp {
            type uint32;
        }
    }

}
