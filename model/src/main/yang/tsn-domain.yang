module tsn-domain {
    yang-version 1.1;
    namespace "urn:ietf:params:xml:ns:netconf:1.0:cnc:cnc-model:tsn-domain";
    prefix "tsn-domain";

    revision "2018-04-01" { // TODO change revision to date of model creation
        description "Initial revision of peregrine model";
    }

    grouping GroupTSNDomain {
        leaf id {
            type uint16;
        }

        leaf name {
            type string;
        }
    }
}
