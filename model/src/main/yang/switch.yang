module switch {
    yang-version 1.1;
    namespace "urn:ietf:params:xml:ns:netconf:1.0:cnc:cnc-model:switch";
    prefix "switch";

    revision "2018-04-01" { // TODO change revision to date of model creation
        description "Initial revision of peregrine model";
    }

    grouping GroupSwitch {

        leaf name {
            type string;
        }

        leaf mac {
            type string;
        }

        container tsn_domain {

            leaf id {
                type uint16;
            }

            leaf as_priority {
                type uint8;
            }
        }

        leaf community {
            type string;
        }

        leaf netconf_username {
            type string;
        }

        leaf netconf_password {
            type string;
        }

        leaf model {
            type string;
        }

        leaf role {
            type enumeration {
              enum none {
                value 0;
              }
              enum core {
                value 1;
              }
              enum edge {
                value 2;
              }
            }
        }
    }
}
