module cnc-functins {
    yang-version 1.1;
    namespace "urn:ietf:params:xml:ns:netconf:1.0:cnc:cnc-functions";
    prefix "dte";

    revision "2018-04-01" { // TODO change revision to date of model creation
        description "Initial revision of peregrine model";
    }

    import ieee802-dot1q-cc-base {
        prefix base;
    }

    import ieee802-dot1q-cc-listener {
        prefix listener;
    }

    import ieee802-dot1q-cc-talker {
        prefix talker;
    }

    import ieee802-dot1q-cc-status {
        prefix status;
    }

    rpc getExamples {
        output {
            list status {
                config false;
                uses status:GroupStatus;
            }
            list talkers {
                config false;
                uses talker:GroupTalker;
            }
            list listeners {
                config false;
                uses listener:GroupListener;
            }
        }
    }

    rpc addCNCTestDataToDataStore {
    }

    rpc removeAllCNCDataFromDataStore {
    }
}
